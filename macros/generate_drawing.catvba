Attribute VB_Name = "模块1"
Sub CATMain(iParameters)
    Dim templatePath As String
    templatePath = iParameters(0)
    
    '--- 1. 验证当前活动文档是否为零件 ---
    If TypeName(CATIA.ActiveDocument) <> "PartDocument" Then
        MsgBox "请先激活一个 CATPart 文档！", vbExclamation
        Exit Sub
    End If
    Dim partDoc As PartDocument
    Set partDoc = CATIA.ActiveDocument

    '--- 2. 定义模板路径 ---
    If Dir(templatePath) = "" Then
        MsgBox "模板文件不存在：" & vbCrLf & templatePath, vbCritical
        Exit Sub
    End If

    '--- 3. 用 NewFrom 创建新图纸 ---
    Dim drawingDoc As DrawingDocument
    Set drawingDoc = CATIA.Documents.NewFrom(templatePath)
    If TypeName(drawingDoc) <> "DrawingDocument" Then
        MsgBox "NewFrom 返回类型错误：" & TypeName(drawingDoc), vbCritical
        Exit Sub
    End If

    '--- 4. ? 将零件属性同步写入图纸文档属性 ---
    Call SyncToDrawingParameters(partDoc, drawingDoc)

    '--- 5. 获取第一张图纸页 ---
    Dim drawingSheet As Object
    Set drawingSheet = drawingDoc.Sheets.Item(1)
    drawingSheet.Activate

    '--- 6. 创建前视图 ---
    Dim views As DrawingViews
    Set views = drawingSheet.views
    Dim frontView As DrawingView
    Set frontView = views.Add("正视图")
    frontView.X = 150
    frontView.Y = 200
    frontView.GenerativeBehavior.Document = partDoc
    frontView.GenerativeBehavior.Update
    
End Sub

Sub SyncToDrawingParameters(partDoc As PartDocument, drawingDoc As DrawingDocument)

    '--- 从零件读取标准属性 ---
    Dim partNumber   As String
    Dim nomenclature As String
    Dim revision     As String

    On Error Resume Next
    partNumber = partDoc.Part.partNumber
    nomenclature = partDoc.Product.nomenclature
    revision = partDoc.Product.revision
    On Error GoTo 0

    '--- 获取零件用户自定义属性集合 ---
    Dim partUserProps As Object
    Set partUserProps = partDoc.Product.UserRefProperties

    '--- 定义需要同步的自定义属性名列表 ---
    '    零件属性名 和 图纸参数名 一一对应
    '--- 定义需要同步的自定义属性名列表 ---
    Dim propNames As Variant
    propNames = Array( _
        "物料编码", _
        "材料", _
        "重量" _
    )

    '--- 获取图纸参数集合 ---
    Dim params As Object
    Set params = drawingDoc.Parameters

    Dim param As Object
    On Error Resume Next

    '--- 同步标准属性 ---
    Set param = params.Item("PartNumber")
    If Not param Is Nothing Then param.Value = partNumber
    Set param = Nothing

    Set param = params.Item("Nomenclature")
    If Not param Is Nothing Then param.Value = nomenclature
    Set param = Nothing

    Set param = params.Item("Revision")
    If Not param Is Nothing Then param.Value = revision
    Set param = Nothing

    '--- 批量同步自定义属性 ---
    Dim i As Integer
    For i = 0 To UBound(propNames)
        Dim propName As String
        propName = propNames(i)

        '从零件读取自定义属性值
        Dim propValue As String
        propValue = ""
        propValue = partUserProps.Item(propName).Value

        '写入图纸同名参数
        Set param = Nothing
        Set param = params.Item(propName)
        If Not param Is Nothing Then
            param.Value = propValue
            Debug.Print "已同步：" & propName & " = " & propValue
        Else
            Debug.Print "图纸中未找到参数：" & propName
        End If
    Next i

    On Error GoTo 0

    '--- 更新图纸显示 ---
    drawingDoc.Update

    Debug.Print "同步完成"

End Sub

Attribute VB_Name = "模块2"
Sub CreateDrawingFromTemplate()
    '--- 1. 验证当前活动文档是否为零件 ---
    If TypeName(CATIA.ActiveDocument) <> "PartDocument" Then
        MsgBox "请先激活一个 CATPart 文档！", vbExclamation
        Exit Sub
    End If
    Dim partDoc As PartDocument
    Set partDoc = CATIA.ActiveDocument

    '--- 2. 定义模板路径 ---
    Dim templatePath As String
    templatePath = "D:\QT-pySide6-CATIA\Output Test\Drawing5.CATDrawing"
    If Dir(templatePath) = "" Then
        MsgBox "模板文件不存在：" & vbCrLf & templatePath, vbCritical
        Exit Sub
    End If

    '--- 3. 用 NewFrom 创建新图纸 ---
    Dim drawingDoc As DrawingDocument
    Set drawingDoc = CATIA.Documents.NewFrom(templatePath)
    If TypeName(drawingDoc) <> "DrawingDocument" Then
        MsgBox "NewFrom 返回类型错误：" & TypeName(drawingDoc), vbCritical
        Exit Sub
    End If

    '--- 4. ? 将零件属性同步写入图纸文档属性 ---
    Call SyncToDrawingParameters(partDoc, drawingDoc)

    '--- 5. 获取第一张图纸页 ---
    Dim drawingSheet As Object
    Set drawingSheet = drawingDoc.Sheets.Item(1)
    drawingSheet.Activate

    '--- 6. 创建前视图 ---
    Dim views As DrawingViews
    Set views = drawingSheet.views
    Dim frontView As DrawingView
    Set frontView = views.Add("正视图")
    frontView.X = 150
    frontView.Y = 200
    frontView.GenerativeBehavior.Document = partDoc
    frontView.GenerativeBehavior.Update

End Sub


Sub SyncToDrawingParameters(partDoc As PartDocument, drawingDoc As DrawingDocument)

    '--- 从零件读取标准属性 ---
    Dim partNumber   As String
    Dim nomenclature As String
    Dim revision     As String

    On Error Resume Next
    partNumber = partDoc.Part.partNumber
    nomenclature = partDoc.Product.nomenclature
    revision = partDoc.Product.revision
    On Error GoTo 0

    '--- 获取零件用户自定义属性集合 ---
    Dim partUserProps As Object
    Set partUserProps = partDoc.Product.UserRefProperties

    '--- 定义需要同步的自定义属性名列表 ---
    '    零件属性名 和 图纸参数名 一一对应
    '--- 定义需要同步的自定义属性名列表 ---
    Dim propNames As Variant
    propNames = Array( _
        "物料编码", _
        "材料", _
        "重量" _
    )

    '--- 获取图纸参数集合 ---
    Dim params As Object
    Set params = drawingDoc.Parameters

    Dim param As Object
    On Error Resume Next

    '--- 同步标准属性 ---
    Set param = params.Item("PartNumber")
    If Not param Is Nothing Then param.Value = partNumber
    Set param = Nothing

    Set param = params.Item("Nomenclature")
    If Not param Is Nothing Then param.Value = nomenclature
    Set param = Nothing

    Set param = params.Item("Revision")
    If Not param Is Nothing Then param.Value = revision
    Set param = Nothing

    '--- 批量同步自定义属性 ---
    Dim i As Integer
    For i = 0 To UBound(propNames)
        Dim propName As String
        propName = propNames(i)

        '从零件读取自定义属性值
        Dim propValue As String
        propValue = ""
        propValue = partUserProps.Item(propName).Value

        '写入图纸同名参数
        Set param = Nothing
        Set param = params.Item(propName)
        If Not param Is Nothing Then
            param.Value = propValue
            Debug.Print "已同步：" & propName & " = " & propValue
        Else
            Debug.Print "图纸中未找到参数：" & propName
        End If
    Next i

    On Error GoTo 0

    '--- 更新图纸显示 ---
    drawingDoc.Update

    Debug.Print "同步完成"

End Sub

Attribute VB_Name = "模块3"
Sub InspectRawLinkText()

    If TypeName(CATIA.ActiveDocument) <> "DrawingDocument" Then
        MsgBox "请先激活 CATDrawing 文档！", vbExclamation
        Exit Sub
    End If

    Dim drawingDoc As DrawingDocument
    Set drawingDoc = CATIA.ActiveDocument

    Dim drawingSheet As Object
    Set drawingSheet = drawingDoc.Sheets.Item(1)

    Dim bgView As DrawingView
    Set bgView = drawingSheet.views.Item(drawingSheet.views.Count)

    Dim texts As DrawingTexts
    Set texts = bgView.texts

    Dim txt As DrawingText
    Dim i As Integer

    ' 输出到立即窗口（View > Immediate Window 查看）
    Debug.Print "====== 文本框原始内容 ======"
    For i = 1 To texts.Count
        Set txt = texts.Item(i)
        Debug.Print "[" & i & "] Name='" & txt.Name & "'"
        Debug.Print "     Text='" & txt.Text & "'"
        Debug.Print ""
    Next i
    Debug.Print "=============================="

    MsgBox "请查看 VBA 立即窗口（View > Immediate Window）获取完整输出", vbInformation

End Sub

Attribute VB_Name = "模块4"
Sub CATMain()

End Sub
