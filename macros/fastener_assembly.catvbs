Option Explicit
' fastener_assembly.catvbs
'
' Called by CATIA Companion -- 工具 > 快速装配紧固件
'
' CATIA Companion passes the fastener CATPart file path as iParameters(0).
' If the value is "" (empty string), the current active document is used.
'
' Workflow:
'   1. Open / reference the fastener CATPart, read its Part Number.
'   2. User selects the cylindrical face (axis) and end face on the fastener.
'   3. Prompt user to switch to the CATProduct assembly.
'   4. User selects the target product / sub-assembly in the tree.
'   5. Assembly loop: select hole cylindrical face -> select pressing plane
'      -> add fastener instance and position it.  Repeat until ESC.
'
' ----------------------------------------------------------------------------

Sub CATMain(iParameters)

    ' ── 1. Resolve fastener path ──────────────────────────────────────────
    Dim fastenerPath
    fastenerPath = CStr(iParameters(0))

    Dim fastenerDoc
    If fastenerPath = "" Then
        ' Use the current active document
        If TypeName(CATIA.ActiveDocument) <> "PartDocument" Then
            MsgBox "当前活动文档不是 CATPart，请先打开紧固件文档。", _
                   vbExclamation, "快速装配紧固件"
            Exit Sub
        End If
        Set fastenerDoc = CATIA.ActiveDocument
        fastenerPath = fastenerDoc.FullName
    Else
        ' Open the specified file
        On Error Resume Next
        Set fastenerDoc = CATIA.Documents.Open(fastenerPath)
        On Error GoTo 0
        If fastenerDoc Is Nothing Then
            MsgBox "无法打开紧固件文件：" & Chr(10) & fastenerPath, _
                   vbCritical, "快速装配紧固件"
            Exit Sub
        End If
    End If

    Dim fastenerPN
    fastenerPN = fastenerDoc.Product.PartNumber

    ' ── 2. Select reference geometry on the fastener ──────────────────────
    Dim sel
    Set sel = CATIA.ActiveDocument.Selection
    sel.Clear

    ' 2a. Select cylindrical face for axis
    Dim cylFilter
    cylFilter = Array("CylindricalFace")
    Dim status
    status = sel.SelectElement2(cylFilter, _
        "请选择紧固件的圆柱面（用于确定轴线方向）", False)
    If status <> "Normal" Then
        MsgBox "已取消选择。", vbInformation, "快速装配紧固件"
        Exit Sub
    End If

    Dim spa
    Set spa = CATIA.ActiveDocument.GetWorkbench("SPAWorkbench")

    Dim cylRef
    Set cylRef = sel.Item(1).Reference
    Dim cylMeas
    Set cylMeas = spa.GetMeasurable(cylRef)

    Dim fastAxis(2)
    cylMeas.GetAxis fastAxis

    Dim fastAxisPt(2)
    cylMeas.GetCOG fastAxisPt

    sel.Clear

    ' 2b. Select end face (planar face on the fastener head)
    Dim faceFilter
    faceFilter = Array("PlanarFace")
    status = sel.SelectElement2(faceFilter, _
        "请选择紧固件的端面（头部压紧面）", False)
    If status <> "Normal" Then
        MsgBox "已取消选择。", vbInformation, "快速装配紧固件"
        Exit Sub
    End If

    Dim faceRef
    Set faceRef = sel.Item(1).Reference
    Dim faceMeas
    Set faceMeas = spa.GetMeasurable(faceRef)

    Dim fastFacePlane(5)
    faceMeas.GetPlane fastFacePlane
    Dim fastFaceNorm(2)
    fastFaceNorm(0) = fastFacePlane(0)
    fastFaceNorm(1) = fastFacePlane(1)
    fastFaceNorm(2) = fastFacePlane(2)

    Dim fastFacePt(2)
    fastFacePt(0) = fastFacePlane(3)
    fastFacePt(1) = fastFacePlane(4)
    fastFacePt(2) = fastFacePlane(5)

    sel.Clear

    ' ── Compute fastener "into-body" axis direction ───────────────────────
    ' If the face normal is roughly aligned with the cylinder axis, the axis
    ' points "outward" like the face normal.  The "into-body" direction is
    ' opposite.
    Dim dotFaFn
    dotFaFn = fastAxis(0) * fastFaceNorm(0) _
            + fastAxis(1) * fastFaceNorm(1) _
            + fastAxis(2) * fastFaceNorm(2)

    ' fa_body: direction pointing from the end-face into the fastener body.
    Dim faBody(2)
    If dotFaFn >= 0 Then
        faBody(0) = -fastAxis(0)
        faBody(1) = -fastAxis(1)
        faBody(2) = -fastAxis(2)
    Else
        faBody(0) = fastAxis(0)
        faBody(1) = fastAxis(1)
        faBody(2) = fastAxis(2)
    End If

    ' ── 3. Find and activate the target assembly document ────────────────
    ' Enumerate all open ProductDocuments so the user never needs to switch
    ' documents manually (switching during SelectElement2 cancels the prompt).
    Dim assemblyDoc
    Dim aIdx, aCount, aNames
    aCount = 0: aNames = ""
    For aIdx = 1 To CATIA.Documents.Count
        If TypeName(CATIA.Documents.Item(aIdx)) = "ProductDocument" Then
            aCount = aCount + 1
            aNames = aNames & aCount & ". " & CATIA.Documents.Item(aIdx).Name & Chr(10)
            Set assemblyDoc = CATIA.Documents.Item(aIdx)
        End If
    Next aIdx

    If aCount = 0 Then
        MsgBox "未找到任何已打开的 CATProduct 装配体文档。" & Chr(10) & _
               "请先打开装配体，再运行本宏。", vbCritical, "快速装配紧固件"
        Exit Sub
    ElseIf aCount > 1 Then
        Dim aChoice
        aChoice = InputBox("检测到多个装配体文档，请输入目标装配体的编号：" & _
                           Chr(10) & Chr(10) & aNames, "快速装配紧固件", "1")
        If aChoice = "" Then
            MsgBox "已取消。", vbInformation, "快速装配紧固件"
            Exit Sub
        End If
        If Not IsNumeric(aChoice) Then
            MsgBox "输入无效，请重新运行宏。", vbExclamation, "快速装配紧固件"
            Exit Sub
        End If
        Dim pickN
        pickN = CInt(aChoice)
        If pickN < 1 Or pickN > aCount Then
            MsgBox "编号超出范围，请重新运行宏。", vbExclamation, "快速装配紧固件"
            Exit Sub
        End If
        Dim bIdx, bCnt
        bCnt = 0
        For bIdx = 1 To CATIA.Documents.Count
            If TypeName(CATIA.Documents.Item(bIdx)) = "ProductDocument" Then
                bCnt = bCnt + 1
                If bCnt = pickN Then
                    Set assemblyDoc = CATIA.Documents.Item(bIdx)
                    Exit For
                End If
            End If
        Next bIdx
    End If

    assemblyDoc.Activate

    ' ── 4. User selects the target product in the assembly tree ──────────
    Set sel = assemblyDoc.Selection
    sel.Clear

    Dim prodFilter
    prodFilter = Array("Product")
    status = sel.SelectElement2(prodFilter, _
        "请在产品结构树中选择紧固件要装入的产品或部件", False)
    If status <> "Normal" Then
        MsgBox "已取消选择。", vbInformation, "快速装配紧固件"
        Exit Sub
    End If

    Dim targetProduct
    Set targetProduct = sel.Item(1).Value
    Dim targetPN
    targetPN = targetProduct.PartNumber
    sel.Clear

    ' ── Compute absolute transform of the target product ─────────────────
    ' Measurements from SPAWorkbench are in root-assembly coordinates.
    ' Position.SetComponents is relative to the parent product.
    ' We need the inverse of the target's absolute transform to convert.
    Dim absR(2, 2)
    Dim absT(2)
    Call ComputeAbsoluteTransform(targetProduct, absR, absT)

    ' ── 5. Assembly loop ─────────────────────────────────────────────────
    Dim count
    count = 0

    Do
        ' 5a. Select hole cylindrical face
        Set sel = CATIA.ActiveDocument.Selection
        sel.Clear

        Dim holeFilter
        holeFilter = Array("CylindricalFace", "RectilinearTriDimFeatEdge", "ConicalFace")
        status = sel.SelectElement2(holeFilter, _
            "选择孔的圆柱面 (" & fastenerPN & " -> " & targetPN & _
            "  已装配:" & count & ")  [ESC终止]", False)
        If status <> "Normal" Then Exit Do

        Set spa = CATIA.ActiveDocument.GetWorkbench("SPAWorkbench")
        Dim holeRef
        Set holeRef = sel.Item(1).Reference
        Dim holeMeas
        Set holeMeas = spa.GetMeasurable(holeRef)

        Dim holeAxis(2)
        Dim holeCOG(2)

        ' GetAxis is not supported on ConicalFace (error 80004005); catch it.
        Dim bAxisOk
        bAxisOk = False
        On Error Resume Next
        Err.Clear
        holeMeas.GetAxis holeAxis
        If Err.Number = 0 Then bAxisOk = True Else Err.Clear
        On Error GoTo 0
        holeMeas.GetCOG holeCOG

        sel.Clear

        If Not bAxisOk Then
            MsgBox "所选面不支持轴向测量（圆锥面不支持 GetAxis）。" & Chr(10) & _
                   "请改为选择孔的圆柱侧面（CylindricalFace）。", _
                   vbExclamation, "快速装配紧固件"
        Else

        ' 5b. Select pressing plane
        Dim planeFilter
        planeFilter = Array("PlanarFace")
        status = sel.SelectElement2(planeFilter, _
            "选择被压紧平面 (" & fastenerPN & " -> " & targetPN & _
            "  已装配:" & count & ")  [ESC终止]", False)
        If status <> "Normal" Then Exit Do

        Dim planeRef
        Set planeRef = sel.Item(1).Reference
        Dim planeMeas
        Set planeMeas = spa.GetMeasurable(planeRef)

        Dim planePlaneArr(5)
        planeMeas.GetPlane planePlaneArr
        Dim planeNorm(2)
        planeNorm(0) = planePlaneArr(0)
        planeNorm(1) = planePlaneArr(1)
        planeNorm(2) = planePlaneArr(2)
        Dim planePt(2)
        planePt(0) = planePlaneArr(3)
        planePt(1) = planePlaneArr(4)
        planePt(2) = planePlaneArr(5)

        sel.Clear

        ' ── Compute line-plane intersection (target point) ────────────────
        Dim denom
        denom = holeAxis(0) * planeNorm(0) _
              + holeAxis(1) * planeNorm(1) _
              + holeAxis(2) * planeNorm(2)

        If Abs(denom) < 0.0001 Then
            MsgBox "孔轴线与压紧平面近似平行，无法计算交点。请重新选择。", _
                   vbExclamation, "快速装配紧固件"
        Else

        Dim tParam
        tParam = ((planePt(0) - holeCOG(0)) * planeNorm(0) _
                + (planePt(1) - holeCOG(1)) * planeNorm(1) _
                + (planePt(2) - holeCOG(2)) * planeNorm(2)) / denom

        Dim targetPt(2)
        targetPt(0) = holeCOG(0) + tParam * holeAxis(0)
        targetPt(1) = holeCOG(1) + tParam * holeAxis(1)
        targetPt(2) = holeCOG(2) + tParam * holeAxis(2)

        ' ── Determine target axis direction ───────────────────────────────
        ' Points from the pressing-plane surface toward the hole interior.
        Dim dx, dy, dz, dist
        dx = holeCOG(0) - targetPt(0)
        dy = holeCOG(1) - targetPt(1)
        dz = holeCOG(2) - targetPt(2)
        dist = Sqr(dx * dx + dy * dy + dz * dz)

        Dim ta(2)
        If dist > 0.001 Then
            ta(0) = dx / dist
            ta(1) = dy / dist
            ta(2) = dz / dist
        Else
            ' holeCOG lies on the plane; fall back to hole-axis direction
            ' pointing away from the plane normal.
            Dim dotHaPn
            dotHaPn = holeAxis(0) * planeNorm(0) _
                    + holeAxis(1) * planeNorm(1) _
                    + holeAxis(2) * planeNorm(2)
            If dotHaPn > 0 Then
                ta(0) = -holeAxis(0): ta(1) = -holeAxis(1): ta(2) = -holeAxis(2)
            Else
                ta(0) = holeAxis(0): ta(1) = holeAxis(1): ta(2) = holeAxis(2)
            End If
        End If

        ' ── Compute rotation matrix  R : faBody -> ta ─────────────────────
        ' Build orthonormal frame F1 from faBody
        Dim f1x(2), f1y(2), f1z(2)
        f1z(0) = faBody(0): f1z(1) = faBody(1): f1z(2) = faBody(2)
        Call BuildFrame(f1z, f1x, f1y)

        ' Build orthonormal frame F2 from ta
        Dim f2x(2), f2y(2), f2z(2)
        f2z(0) = ta(0): f2z(1) = ta(1): f2z(2) = ta(2)
        Call BuildFrame(f2z, f2x, f2y)

        ' R = F2 * F1^T   (maps faBody -> ta and preserves orthonormality)
        Dim R(2, 2)
        Dim ri, rj
        For ri = 0 To 2
            For rj = 0 To 2
                R(ri, rj) = F2Col(ri, 0, f2x, f2y, f2z) * F1Col(rj, 0, f1x, f1y, f1z) _
                          + F2Col(ri, 1, f2x, f2y, f2z) * F1Col(rj, 1, f1x, f1y, f1z) _
                          + F2Col(ri, 2, f2x, f2y, f2z) * F1Col(rj, 2, f1x, f1y, f1z)
            Next
        Next

        ' ── Compute translation ───────────────────────────────────────────
        ' R * fastFacePt + T = targetPt   =>  T = targetPt - R * fastFacePt
        Dim rfp(2)
        rfp(0) = R(0, 0) * fastFacePt(0) + R(0, 1) * fastFacePt(1) + R(0, 2) * fastFacePt(2)
        rfp(1) = R(1, 0) * fastFacePt(0) + R(1, 1) * fastFacePt(1) + R(1, 2) * fastFacePt(2)
        rfp(2) = R(2, 0) * fastFacePt(0) + R(2, 1) * fastFacePt(1) + R(2, 2) * fastFacePt(2)

        Dim Tvec(2)
        Tvec(0) = targetPt(0) - rfp(0)
        Tvec(1) = targetPt(1) - rfp(1)
        Tvec(2) = targetPt(2) - rfp(2)

        ' ── Convert from root-assembly coords to target-product-local ─────
        ' localR = absR^T * R ;  localT = absR^T * (Tvec - absT)
        Dim localR(2, 2)
        Dim localT(2)
        Dim li, lj, lk
        For li = 0 To 2
            For lj = 0 To 2
                localR(li, lj) = 0
                For lk = 0 To 2
                    localR(li, lj) = localR(li, lj) + absR(lk, li) * R(lk, lj)
                Next
            Next
        Next
        Dim diffT(2)
        diffT(0) = Tvec(0) - absT(0)
        diffT(1) = Tvec(1) - absT(1)
        diffT(2) = Tvec(2) - absT(2)
        For li = 0 To 2
            localT(li) = 0
            For lk = 0 To 2
                localT(li) = localT(li) + absR(lk, li) * diffT(lk)
            Next
        Next

        ' ── Add fastener component ────────────────────────────────────────
        Dim products
        Set products = targetProduct.Products

        Dim pathArray(0)
        pathArray(0) = fastenerPath
        products.AddComponentsFromFiles pathArray, "All"

        ' The newly added instance is the last item
        Dim newComp
        Set newComp = products.Item(products.Count)

        ' ── Set position (relative to parent) ────────────────────────────
        ' CATIA Position array layout:
        '   0-2  = local X axis in parent coords
        '   3-5  = local Y axis in parent coords
        '   6-8  = local Z axis in parent coords
        '   9-11 = origin in parent coords
        Dim posMatrix(11)
        ' Local X axis (column 0 of localR)
        posMatrix(0)  = localR(0, 0)
        posMatrix(1)  = localR(1, 0)
        posMatrix(2)  = localR(2, 0)
        ' Local Y axis (column 1 of localR)
        posMatrix(3)  = localR(0, 1)
        posMatrix(4)  = localR(1, 1)
        posMatrix(5)  = localR(2, 1)
        ' Local Z axis (column 2 of localR)
        posMatrix(6)  = localR(0, 2)
        posMatrix(7)  = localR(1, 2)
        posMatrix(8)  = localR(2, 2)
        ' Origin
        posMatrix(9)  = localT(0)
        posMatrix(10) = localT(1)
        posMatrix(11) = localT(2)

        newComp.Position.SetComponents posMatrix

        count = count + 1
        CATIA.StatusBar = "已装配 " & count & " 个 " & fastenerPN & " -> " & targetPN

        End If  ' Abs(denom) >= 0.0001
        End If  ' bAxisOk
    Loop

    CATIA.StatusBar = "装配完成！共装配 " & count & " 个 " & fastenerPN
    MsgBox "装配完成！" & Chr(10) & _
           "共装配 " & count & " 个 " & fastenerPN & " 到 " & targetPN & "。", _
           vbInformation, "快速装配紧固件"

End Sub


' ============================================================================
' Helper: Build an orthonormal frame {outX, outY, inZ} from a given Z axis.
' ============================================================================
Sub BuildFrame(inZ, outX, outY)
    ' Pick a reference vector not (anti-)parallel to inZ
    Dim refV(2)
    If Abs(inZ(0)) < 0.9 Then
        refV(0) = 1: refV(1) = 0: refV(2) = 0
    Else
        refV(0) = 0: refV(1) = 1: refV(2) = 0
    End If

    ' outX = cross(inZ, refV), then normalise
    outX(0) = inZ(1) * refV(2) - inZ(2) * refV(1)
    outX(1) = inZ(2) * refV(0) - inZ(0) * refV(2)
    outX(2) = inZ(0) * refV(1) - inZ(1) * refV(0)
    Dim xLen
    xLen = Sqr(outX(0) * outX(0) + outX(1) * outX(1) + outX(2) * outX(2))
    If xLen < 0.000000000001 Then
        ' inZ was a zero vector; return a safe default frame to avoid crash
        outX(0) = 1: outX(1) = 0: outX(2) = 0
        outY(0) = 0: outY(1) = 1: outY(2) = 0
        Exit Sub
    End If
    outX(0) = outX(0) / xLen
    outX(1) = outX(1) / xLen
    outX(2) = outX(2) / xLen

    ' outY = cross(inZ, outX)
    outY(0) = inZ(1) * outX(2) - inZ(2) * outX(1)
    outY(1) = inZ(2) * outX(0) - inZ(0) * outX(2)
    outY(2) = inZ(0) * outX(1) - inZ(1) * outX(0)
End Sub


' ============================================================================
' Helper: Return the (row)-th element of column (col) of the frame {vx,vy,vz}.
' ============================================================================
Function F1Col(row, col, vx, vy, vz)
    Select Case col
        Case 0: F1Col = vx(row)
        Case 1: F1Col = vy(row)
        Case 2: F1Col = vz(row)
    End Select
End Function

Function F2Col(row, col, vx, vy, vz)
    Select Case col
        Case 0: F2Col = vx(row)
        Case 1: F2Col = vy(row)
        Case 2: F2Col = vz(row)
    End Select
End Function


' ============================================================================
' Helper: Compute the absolute transform of *prod* in the root assembly.
'
' Walks up the product tree, chaining Position.GetComponents matrices until
' the root product is reached.
'
' On return:  point_in_root = outR * point_in_local + outT
' ============================================================================
Sub ComputeAbsoluteTransform(prod, outR, outT)

    ' Start with identity
    outR(0, 0) = 1: outR(0, 1) = 0: outR(0, 2) = 0
    outR(1, 0) = 0: outR(1, 1) = 1: outR(1, 2) = 0
    outR(2, 0) = 0: outR(2, 1) = 0: outR(2, 2) = 1
    outT(0) = 0: outT(1) = 0: outT(2) = 0

    Dim rootProd
    Set rootProd = CATIA.ActiveDocument.Product

    Dim current
    Set current = prod

    ' Walk up: current -> parent -> ... -> root
    On Error Resume Next
    Do
        ' If we have reached the root product, stop.
        If current.PartNumber = rootProd.PartNumber Then
            ' Double-check by COM identity where possible
            Dim testName
            testName = ""
            testName = current.Parent.Parent.PartNumber
            If Err.Number <> 0 Then
                Err.Clear
                Exit Do   ' current.Parent.Parent failed => root
            End If
            ' If current IS rootProd (same object), stop
            If current.Name = rootProd.Name Then Exit Do
        End If

        ' Read position of current relative to its parent
        Dim pos(11)
        current.Position.GetComponents pos
        If Err.Number <> 0 Then
            Err.Clear
            Exit Do
        End If

        ' Extract rotation Rl and translation Tl from pos
        Dim Rl(2, 2)
        Rl(0, 0) = pos(0):  Rl(1, 0) = pos(1):  Rl(2, 0) = pos(2)
        Rl(0, 1) = pos(3):  Rl(1, 1) = pos(4):  Rl(2, 1) = pos(5)
        Rl(0, 2) = pos(6):  Rl(1, 2) = pos(7):  Rl(2, 2) = pos(8)
        Dim Tl(2)
        Tl(0) = pos(9): Tl(1) = pos(10): Tl(2) = pos(11)

        ' Chain:  newR = Rl * outR ,  newT = Rl * outT + Tl
        Dim newR(2, 2), newT(2)
        Dim ci, cj, ck
        For ci = 0 To 2
            For cj = 0 To 2
                newR(ci, cj) = 0
                For ck = 0 To 2
                    newR(ci, cj) = newR(ci, cj) + Rl(ci, ck) * outR(ck, cj)
                Next
            Next
        Next
        For ci = 0 To 2
            newT(ci) = Tl(ci)
            For ck = 0 To 2
                newT(ci) = newT(ci) + Rl(ci, ck) * outT(ck)
            Next
        Next

        ' Overwrite
        For ci = 0 To 2
            For cj = 0 To 2
                outR(ci, cj) = newR(ci, cj)
            Next
            outT(ci) = newT(ci)
        Next

        ' Move up: Product -> Products collection -> parent Product
        Set current = current.Parent.Parent
        If Err.Number <> 0 Then
            Err.Clear
            Exit Do
        End If
    Loop
    On Error GoTo 0

End Sub
