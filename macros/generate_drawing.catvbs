Option Explicit
' generate_drawing.catvbs
'
' Called by CATIA Companion -- Drawing > Generate Drawing from CATPart/CATProduct.
'
' CATIA Companion passes the selected CATDrawing template path as a plain
' string in TemplatePath.  The macro uses it directly as tp.
' When invoked without a parameter, CATIA itself prompts the user.
'
' ----------------------------------------------------------------------------

Sub CATMain(TemplatePath)

	'--- 1. 定义模板路径 ---
	Dim tp
	tp = TemplatePath
	
	'--- 2. 验证当前活动文档是否为零件 ---
	If TypeName(CATIA.ActiveDocument) <> "PartDocument" Then
		MsgBox "请先激活一个 CATPart 文档！", vbExclamation
		Exit Sub
	End If
	Dim partDoc
	Set partDoc = CATIA.ActiveDocument
	'--- 3. 用 NewFrom 创建新图纸 ---
	Dim drawingDoc
	Set drawingDoc = CATIA.Documents.NewFrom(CStr(tp))

	If TypeName(drawingDoc) <> "DrawingDocument" Then
		MsgBox "NewFrom 返回类型错误：" & TypeName(drawingDoc), vbCritical
		Exit Sub
	End If

	'--- 4. 同步零件属性到图纸参数 ---
	Call SyncToDrawingParameters(partDoc, drawingDoc)

	'--- 5. 获取第一张图纸页 ---
	Dim drawingSheet
	Set drawingSheet = drawingDoc.Sheets.Item(1)
	drawingSheet.Activate

	'--- 6. 创建前视图 ---
	'Dim views
	'Set views = drawingSheet.Views

	'Dim frontView
	'Set frontView = views.Add("正视图")
	'frontView.X = 150
	'frontView.Y = 200
	'frontView.GenerativeBehavior.Document = partDoc
	'frontView.GenerativeBehavior.Update

End Sub

Sub SyncToDrawingParameters(partDoc, drawingDoc)

	'--- 调试日志收集 ---
	Dim logMsg
	logMsg = ""

	'--- 从零件读取标准属性 ---
	Dim partNumber
	Dim nomenclature
	Dim revision

	On Error Resume Next
	partNumber   = partDoc.Product.PartNumber
	nomenclature = partDoc.Product.Nomenclature
	revision     = partDoc.Product.Revision
	On Error GoTo 0

	'--- 获取零件用户自定义属性集合 ---
	Dim partUserProps
	Set partUserProps = Nothing
	On Error Resume Next
	Set partUserProps = partDoc.Product.UserRefProperties
	On Error GoTo 0

	If partUserProps Is Nothing Then
		logMsg = logMsg & "零件无用户自定义属性集合" & Chr(10)
	End If

	'--- 定义需要同步的自定义属性名列表 ---
	Dim propNames
	propNames = Array( _
		"物料编码", _
		"材料", _
		"重量" _
	)

	'--- 获取图纸参数集合 ---
	Dim params
	Set params = drawingDoc.Parameters

	Dim param
	On Error Resume Next

	'--- 同步标准属性 ---
	Set param = params.Item("PartNumber")
	If Not param Is Nothing Then
		param.Value = partNumber
		logMsg = logMsg & "已同步： PartNumber = " & partNumber & Chr(10)
	Else
		logMsg = logMsg & "图纸中未找到参数 PartNumber" & Chr(10)
	End If
	Set param = Nothing

	Set param = params.Item("Nomenclature")
	If Not param Is Nothing Then
		param.Value = nomenclature
		logMsg = logMsg & "已同步： Nomenclature = " & nomenclature & Chr(10)
	Else
		logMsg = logMsg & "图纸中未找到参数 Nomenclature" & Chr(10)
	End If
	Set param = Nothing

	Set param = params.Item("Revision")
	If Not param Is Nothing Then
		param.Value = revision
		logMsg = logMsg & "已同步： Revision = " & revision & Chr(10)
	Else
		logMsg = logMsg & "图纸中未找到参数 Revision" & Chr(10)
	End If
	Set param = Nothing

	On Error GoTo 0

	'--- 批量同步自定义属性 ---
	Dim i
	Dim propName
	Dim propValue
	Dim bPropExists
	Dim tmpProp
	Dim userInput

	For i = 0 To UBound(propNames)
		propName    = propNames(i)
		propValue   = ""
		bPropExists = False

		'--- 尝试从零件读取属性值 ---
		If Not partUserProps Is Nothing Then
			On Error Resume Next
			Err.Clear
			Set tmpProp = partUserProps.Item(propName)
			If Err.Number = 0 Then
				If Not tmpProp Is Nothing Then
					propValue   = tmpProp.Value
					bPropExists = True
				End If
			End If
			Set tmpProp = Nothing
			On Error GoTo 0
		End If

		'--- 属性不存在时弹窗提示用户填写 ---
		If Not bPropExists Then
			userInput = InputBox( _
				"零件 """ & partNumber & """ 中未找到用户自定义属性 """ & propName & """。" & Chr(10) & _
				"请输入该属性的值（留空则以空值写入图纸）：", _
				"补充缺失属性 - " & propName, "")
			propValue = userInput

			'--- 将填入的值写回零件属性 ---
			If propValue <> "" Then
				On Error Resume Next
				If partUserProps Is Nothing Then
					Set partUserProps = partDoc.Product.UserRefProperties
				End If
				If Not partUserProps Is Nothing Then
					partUserProps.CreateString propName, propValue
				End If
				On Error GoTo 0
			End If

			logMsg = logMsg & "属性 " & propName & " 不存在，用户输入值：" & propValue & Chr(10)
		End If

		'--- 写入图纸参数 ---
		On Error Resume Next
		Set param = Nothing
		Set param = params.Item(propName)
		If Not param Is Nothing Then
			param.Value = propValue
			logMsg = logMsg & "已同步：" & propName & " = " & propValue & Chr(10)
		Else
			logMsg = logMsg & "图纸中未找到参数：" & propName & Chr(10)
		End If
		On Error GoTo 0
	Next

	'--- 更新图纸显示 ---
	drawingDoc.Update
	logMsg = logMsg & "同步完成"

	MsgBox logMsg, vbInformation, "同步日志"

End Sub
