Option Explicit

' ============================================================
' create_inertia_relations.catvbs   (VBScript / CATScript)
'
' 功能概述：
'   在 CATIA V5 零件文档中创建"质量特性参数绑定"。
'   脚本会把零件的 "惯量包络体.1" Keep 测量结果（体积、密度、质量、重心、
'   转动惯量等）通过公式绑定到以 MP_* 开头的用户参数中，
'   供外部程序直接读取，而无需再次运行 SPA。
'
' 参数写出清单（全部为无量纲实数，单位在参数名中标注）：
'   MP_Volume_cm3       — 体积，cm³
'   MP_Density_g_cm3    — 密度，g/cm³
'   MP_Mass_g           — 质量，g
'   MP_COGx_mm          — 重心 X 坐标，mm（零件局部坐标系）
'   MP_COGy_mm          — 重心 Y 坐标，mm
'   MP_COGz_mm          — 重心 Z 坐标，mm
'   MP_Ixx_gxmm2 ~ MP_Iyz_gxmm2 — 惯量张量分量，g·mm²（重心处，零件局部轴）
'
' 先决条件：
'   零件必须已执行"测量惯量"并勾选"保持测量"，
'   从而在参数树中生成 "惯量包络体.1\质量" 等参数。
'   若该参数不存在，脚本静默退出（不弹对话框），以便外部批量调用。
'
' iParameters 用法（由 SystemService.ExecuteScript 传入）：
'   iParameters(0) — 目标零件的零件号（PartNumber，可选）。
'     · 若提供且非空：脚本遍历已打开的 PartDocument，找到
'       doc.Part.PartNumber 与传入值匹配的文档并激活，再执行绑定。
'     · 若为空或省略：对 CATIA 当前活动文档执行绑定。
'
' 幂等性：
'   MP_* 参数和公式若已存在则复用/跳过，不会重复创建，可安全重复运行。
' ============================================================

Sub CATMain(iParameters)

    ' ── 获取 CATIA 应用对象 ────────────────────────────────────────────────
    Dim CATIA
    Set CATIA = GetObject(, "CATIA.Application")

    ' ── 解析 iParameters：目标零件号（PartNumber，可选）───────────────
    ' VBScript 下 iParameters 可能是数组、也可能是单值；这里做容错读取。
    Dim targetPN
    targetPN = ""

    On Error Resume Next
    targetPN = CStr(iParameters)
    Err.Clear
    On Error GoTo 0

    ' ── 定位目标 PartDocument ──────────────────────────────────────────────
    Dim partDoc
    Set partDoc = Nothing

    If targetPN <> "" Then
        ' 按零件号在已打开文档中查找，并激活
        Dim i, found
        found = False

        On Error Resume Next
        For i = 1 To CATIA.Documents.Count
            Dim doc
            Set doc = CATIA.Documents.Item(i)
            If TypeName(doc) = "PartDocument" Then
                Dim pn
                pn = doc.Product.PartNumber
                If pn = targetPN Then
                    Set partDoc = doc
                    partDoc.Activate
                    found = True
                    Exit For
                End If
            End If
        Next
        On Error GoTo 0

        ' 没找到目标文档：静默退出
        If Not found Then Exit Sub
    Else
        MsgBox "未传入零件号：使用当前活动文档进行参数绑定。"
        If CATIA.Documents.Count = 0 Then Exit Sub
        If TypeName(CATIA.ActiveDocument) <> "PartDocument" Then Exit Sub
        Set partDoc = CATIA.ActiveDocument
    End If

    ' ── 获取零件的 Parameters / Relations 集合 ──────────────────────────────
    Dim part
    Set part = partDoc.Part

    Dim params
    Set params = part.Parameters

    Dim rels
    Set rels = part.Relations

    ' 惯量包络体的参数名前缀（CATIA 生成的 Keep 测量节点名称）
    '
    ' 参数全名的前缀规则：
    '   · 通过 Documents 集合按零件号定位文档时（targetPN 非空），
    '     CATIA 在 Part.Parameters.Item() 路径中以"零件号\"作为顶层命名空间，
    '     因此前缀为 targetPN & "\惯量包络体.1\"。
    '   · 直接操作当前活动文档时（targetPN 为空），CATIA 使用相对于
    '     Part 本身的局部路径，不含零件号前缀，前缀为 "惯量包络体.1\"。
    Dim srcPrefix
    If targetPN <> "" Then
        srcPrefix = targetPN & "\惯量包络体.1\"
    Else
        srcPrefix = "惯量包络体.1\"
    End If
    ' ── 先决条件校验：检查 Keep 测量参数是否存在 ───────────────────────────
    If Not ParameterExists(params, srcPrefix & "质量") Then Exit Sub
    ' ── 第 1 步：确保 MP_* 参数存在（不存在则创建，存在则复用）─────────────
    Dim pVolume:  Set pVolume  = GetOrCreateReal(params, "MP_Volume_cm3")
    Dim pDensity: Set pDensity = GetOrCreateReal(params, "MP_Density_g_cm3")
    Dim pMass:    Set pMass    = GetOrCreateReal(params, "MP_Mass_g")

    Dim pCOGx: Set pCOGx = GetOrCreateReal(params, "MP_COGx_mm")
    Dim pCOGy: Set pCOGy = GetOrCreateReal(params, "MP_COGy_mm")
    Dim pCOGz: Set pCOGz = GetOrCreateReal(params, "MP_COGz_mm")

    Dim pIxx: Set pIxx = GetOrCreateReal(params, "MP_Ixx_gxmm2")
    Dim pIyy: Set pIyy = GetOrCreateReal(params, "MP_Iyy_gxmm2")
    Dim pIzz: Set pIzz = GetOrCreateReal(params, "MP_Izz_gxmm2")
    Dim pIxy: Set pIxy = GetOrCreateReal(params, "MP_Ixy_gxmm2")
    Dim pIxz: Set pIxz = GetOrCreateReal(params, "MP_Ixz_gxmm2")
    Dim pIyz: Set pIyz = GetOrCreateReal(params, "MP_Iyz_gxmm2")

    ' ── 第 2 步：确保公式存在（不存在则创建，存在则保留现有公式）──────────
    ' 注意：单位常量字符串要与你环境一致：
    '   体积：1cm3
    '   密度：你原文写的是 1g_cm3（下划线）；如果你环境实际是 1g/cm3，请改成 "1g/cm3"
    CreateFormulaIfMissing rels, "F_MP_Volume_cm3",    pVolume,  StdExpr(srcPrefix, "体积",  "1cm3")
    CreateFormulaIfMissing rels, "F_MP_Density_g_cm3", pDensity, StdExpr(srcPrefix, "密度",  "1g_cm3")
    CreateFormulaIfMissing rels, "F_MP_Mass_g",        pMass,    StdExpr(srcPrefix, "质量",  "1g")

    CreateFormulaIfMissing rels, "F_MP_COGx_mm", pCOGx, StdExpr(srcPrefix, "Gx",   "1mm")
    CreateFormulaIfMissing rels, "F_MP_COGy_mm", pCOGy, StdExpr(srcPrefix, "Gy",   "1mm")
    CreateFormulaIfMissing rels, "F_MP_COGz_mm", pCOGz, StdExpr(srcPrefix, "Gz",   "1mm")

    CreateFormulaIfMissing rels, "F_MP_Ixx_gxmm2", pIxx, StdExpr(srcPrefix, "IoxG", "1gxmm2")
    CreateFormulaIfMissing rels, "F_MP_Iyy_gxmm2", pIyy, StdExpr(srcPrefix, "IoyG", "1gxmm2")
    CreateFormulaIfMissing rels, "F_MP_Izz_gxmm2", pIzz, StdExpr(srcPrefix, "IozG", "1gxmm2")
    CreateFormulaIfMissing rels, "F_MP_Ixy_gxmm2", pIxy, StdExpr(srcPrefix, "IxyG", "1gxmm2")
    CreateFormulaIfMissing rels, "F_MP_Ixz_gxmm2", pIxz, StdExpr(srcPrefix, "IxzG", "1gxmm2")
    CreateFormulaIfMissing rels, "F_MP_Iyz_gxmm2", pIyz, StdExpr(srcPrefix, "IyzG", "1gxmm2")

    ' 注：通常不需要显式 part.Update；下次更新时公式会自动计算。
End Sub

' ============================================================
' StdExpr — 生成标准公式右侧表达式字符串
' 格式：`<srcPrefix><fieldName>` / <unitConst>
' ============================================================
Private Function StdExpr(srcPrefix, fieldName, unitConst)
    StdExpr = "`" & srcPrefix & fieldName & "` / " & unitConst
End Function

' ============================================================
' CreateFormulaIfMissing — 只在同名公式不存在时才创建
' - VBScript 不能使用强类型声明（As Formula/As Parameter 等）
' ============================================================
Private Sub CreateFormulaIfMissing(rels, fName, targetParam, rhsExpr)

    ' 守卫：targetParam 为 Nothing 或非对象时静默跳过，避免 rels.CreateFormula 崩溃。
    If Not IsObject(targetParam) Or targetParam Is Nothing Then Exit Sub

    On Error Resume Next
    Dim f
    Set f = rels.Item(fName)
    If Err.Number = 0 And Not f Is Nothing Then
        Err.Clear
        On Error GoTo 0
        Exit Sub
    End If
    Err.Clear
    On Error GoTo 0

    ' 公式不存在，尝试创建；失败时通过 MsgBox 报告错误，便于诊断。
    On Error Resume Next
    Err.Clear
    rels.CreateFormula fName, "", targetParam, rhsExpr
    Dim createErr: createErr = Err.Number
    Dim createDesc: createDesc = Err.Description
    Err.Clear
    On Error GoTo 0

    If createErr <> 0 Then
        MsgBox "创建公式 [" & fName & "] 失败" & vbCrLf & _
               "表达式：" & rhsExpr & vbCrLf & _
               "错误 " & createErr & "：" & createDesc, _
               vbExclamation, "create_inertia_relations"
    End If
End Sub

' ============================================================
' ParameterExists — 检查指定全名的参数是否存在
' ============================================================
Private Function ParameterExists(params, fullName)
    On Error Resume Next
    Dim p
    Set p = params.Item(fullName)
    ParameterExists = (Err.Number = 0 And Not p Is Nothing)
    Err.Clear
    On Error GoTo 0
End Function

' ============================================================
' GetOrCreateReal — 获取或新建一个实数参数
' ============================================================
Private Function GetOrCreateReal(params, paramName)
    On Error Resume Next
    Dim p
    Set p = params.Item(paramName)
    ' 注意：不在此处 On Error GoTo 0，因为若 Item() 出错 p 仍为 Empty（非 Nothing），
    ' 对 Empty 变量使用 Is Nothing 会触发“缺少对象”错误 424。
    ' 用 IsObject 先判断 p 是否为有效对象引用。
    If Not IsObject(p) Or p Is Nothing Then
        Err.Clear
        Set p = params.CreateReal(paramName, 0)
    End If
    ' 保持 On Error Resume Next 直到赋值完成，防止 p 仍为 Empty 时抛出错误 424。
    Set GetOrCreateReal = p
    Err.Clear
    On Error GoTo 0
End Function
