Option Explicit

' ============================================================
' read_inertia_direct.catvbs   (VBScript / CATScript)
'
' 功能概述：
'   诊断宏——遍历 Part.Parameters，按关键字（SEARCH_KEYWORD）过滤参数，
'   列出其完整名称、类型和当前值（每页 20 条，多页依次弹出），
'   帮助确认 CATIA 内部的实际参数命名规则。
'   · 将 SEARCH_KEYWORD 改为其他字符串可查找别的参数。
'   · 将 SEARCH_KEYWORD 置为 "" 则显示全部参数。
'
' iParameters 用法（由 SystemService.ExecuteScript 传入，也可手动运行）：
'   iParameters — 目标零件的零件编号（PartNumber 字符串，可选）。
'     · 若提供且非空：在已打开的 PartDocument 中按 PartNumber 定位。
'     · 若为空或省略：使用当前活动文档。
' ============================================================

Sub CATMain(PartNumber)

    ' ── 获取 CATIA 应用对象 ───────────────────────────────────────────────────
    Dim CATIA
    Set CATIA = GetObject(, "CATIA.Application")

    ' ── 解析 iParameters：目标零件编号（PartNumber，可选）─────────────────────
    Dim targetPN
    targetPN = ""
    On Error Resume Next
    targetPN = CStr(iParameters)
    Err.Clear
    On Error GoTo 0

    ' ── 定位目标 PartDocument ────────────────────────────────────────────────
    Dim partDoc
    Set partDoc = Nothing

    If targetPN <> "" Then
        Dim i, found
        found = False
        On Error Resume Next
        For i = 1 To CATIA.Documents.Count
            Dim doc
            Set doc = CATIA.Documents.Item(i)
            If TypeName(doc) = "PartDocument" Then
                Dim pn
                pn = doc.Product.PartNumber
                If pn = targetPN Then
                    Set partDoc = doc
                    partDoc.Activate
                    found = True
                    Exit For
                End If
            End If
        Next
        On Error GoTo 0
        If Not found Then
            MsgBox "未找到零件编号为 [" & targetPN & "] 的 PartDocument，已退出。", _
                   vbExclamation, "read_inertia_direct"
            Exit Sub
        End If
    Else
        If CATIA.Documents.Count = 0 Then
            MsgBox "没有已打开的文档，已退出。", vbExclamation, "read_inertia_direct"
            Exit Sub
        End If
        If TypeName(CATIA.ActiveDocument) <> "PartDocument" Then
            MsgBox "当前活动文档不是 PartDocument（类型=" & TypeName(CATIA.ActiveDocument) & "），已退出。", _
                   vbExclamation, "read_inertia_direct"
            Exit Sub
        End If
        Set partDoc = CATIA.ActiveDocument
    End If

    Dim part
    Set part = partDoc.Part

    Dim actualPN
    On Error Resume Next
    actualPN = part.PartNumber
    If Err.Number <> 0 Then actualPN = "(读取失败)"
    Err.Clear
    On Error GoTo 0

    ' =========================================================================
    ' 路径 A：遍历 Part.Parameters，按 SEARCH_KEYWORD 过滤参数（分页输出）
    ' =========================================================================
    Call EnumParameters(part, actualPN)

End Sub


' =============================================================================
' 路径 A — 遍历 Part.Parameters，找出所有含关键字的参数
'
' CATIA 内部对保持测量参数的命名规则因版本和语言包而异，
' 本路径直接枚举全部参数并过滤，得到实际可用的完整名称和当前值，
' 是确认其他路径中前缀/字段名是否正确的基础。
'
' 注：保持测量参数值由 CATIA 以混合单位存储（质量 kg、坐标 mm、惯量 kg·m²）；
'     程序读取后将坐标 ÷1000 换算为 m，实现全 SI 内部存储。
' =============================================================================
Private Sub EnumParameters(part, actualPN)
    On Error Resume Next

    ' ── 搜索关键字 ──────────────────────────────────────────────────────────────
    ' 修改此变量可查找其他参数；置为空字符串("")则显示全部参数
    Dim SEARCH_KEYWORD
    SEARCH_KEYWORD = "惯量包络体"

    ' 每页最多显示的参数条数
    Const PAGE_SIZE = 20

    Dim params
    Set params = part.Parameters

    Dim total
    total = 0
    On Error Resume Next
    total = params.Count
    Err.Clear
    On Error GoTo 0

    If total = 0 Then
        MsgBox "Part.Parameters 为空或读取失败，跳过。", _
               vbExclamation, "直接读取质量信息"
        Exit Sub
    End If

    ' 收集所有匹配行到数组（VBScript 用 ReDim Preserve 动态扩容）
    Dim hitLines()
    ReDim hitLines(0)
    Dim hitCount
    hitCount = 0

    Dim searchUpper
    searchUpper = UCase(SEARCH_KEYWORD)

    Dim j
    For j = 1 To total
        On Error Resume Next
        Dim p
        Set p = params.Item(j)
        If Err.Number <> 0 Or Not IsObject(p) Then
            Err.Clear
        Else
            Dim pName, pType, pVal
            pName = ""
            pType = ""
            pVal  = ""

            pName = p.Name
            If Err.Number <> 0 Then pName = "?(Name错误)": Err.Clear

            ' 用 TypeName 获取 COM 类型字符串，通常为 "RealParam"、"LengthParam" 等
            pType = TypeName(p)
            If Err.Number <> 0 Then pType = "?(Type错误)": Err.Clear

            On Error Resume Next
            pVal = CStr(p.Value)
            If Err.Number <> 0 Then pVal = "?(Value错误)": Err.Clear

            ' 过滤：SEARCH_KEYWORD 为空则匹配全部；否则参数名须含该关键字
            Dim nameUp
            nameUp = UCase(pName)
            Dim isMatch
            isMatch = False
            If SEARCH_KEYWORD = "" Then
                isMatch = True
            ElseIf InStr(nameUp, searchUpper) > 0 Then
                isMatch = True
            End If

            If isMatch Then
                hitCount = hitCount + 1
                ReDim Preserve hitLines(hitCount - 1)
                hitLines(hitCount - 1) = hitCount & ". " & pName & vbCrLf & _
                                         "   类型=" & pType & "  值=" & pVal
            End If
        End If
        Err.Clear
    Next
    On Error GoTo 0

    If hitCount = 0 Then
        ' 若无命中，再扫描一遍，输出前 30 个参数名供人工核查
        Dim filterDesc
        If SEARCH_KEYWORD = "" Then
            filterDesc = "（空关键字，共 " & total & " 个参数，全部读取失败）"
        Else
            filterDesc = "未找到含""" & SEARCH_KEYWORD & """的参数（共 " & total & " 个参数）"
        End If

        Dim sample
        sample = ""
        Dim sCount
        sCount = 0
        For j = 1 To total
            If sCount >= 30 Then Exit For
            On Error Resume Next
            Dim ps
            Set ps = params.Item(j)
            If Err.Number = 0 And IsObject(ps) Then
                Dim psName
                psName = ps.Name
                If Err.Number = 0 Then
                    sample = sample & psName & vbCrLf
                    sCount = sCount + 1
                End If
            End If
            Err.Clear
        Next
        On Error GoTo 0
        MsgBox filterDesc & "。" & vbCrLf & vbCrLf & _
               "前 " & sCount & " 个参数名（供参考）：" & vbCrLf & sample, _
               vbExclamation, "直接读取质量信息"
    Else
        ' 分页显示：每页 PAGE_SIZE 条
        Dim totalPages
        totalPages = Int((hitCount + PAGE_SIZE - 1) / PAGE_SIZE)

        Dim pg
        For pg = 1 To totalPages
            Dim startIdx, endIdx
            startIdx = (pg - 1) * PAGE_SIZE
            endIdx   = startIdx + PAGE_SIZE - 1
            If endIdx >= hitCount Then endIdx = hitCount - 1

            Dim pageHdr
            If SEARCH_KEYWORD = "" Then
                pageHdr = "全部参数（第 " & pg & "/" & totalPages & " 页，共 " & hitCount & " 个）："
            Else
                pageHdr = "含""" & SEARCH_KEYWORD & """的参数（第 " & pg & "/" & totalPages & " 页，共 " & hitCount & " 个）："
            End If

            Dim pageBody
            pageBody = ""
            Dim k
            For k = startIdx To endIdx
                pageBody = pageBody & hitLines(k) & vbCrLf
            Next

            MsgBox pageHdr & vbCrLf & vbCrLf & pageBody, _
                   vbInformation, "直接读取质量信息"
        Next
    End If
End Sub
