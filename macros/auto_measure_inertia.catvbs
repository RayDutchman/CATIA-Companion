Option Explicit

' ============================================================
' auto_measure_inertia.catvbs   (VBScript / CATScript)
'
' 功能概述：
'   路径 A 测试宏 — 通过 SPAWorkbench.GetMeasurable() 接口对零件实体
'   执行实时惯量测量（非保持测量），并将结果弹窗显示，用于验证 SPA API
'   在当前 CATIA 版本中是否可用及返回值是否正确。
'
'   · 使用 Measurable 对象的标准属性/方法读取：
'       .Mass                  — 质量，kg
'       .GetCOGPosition(arr)   — 重心坐标数组（mm），arr(0)=Gx, arr(1)=Gy, arr(2)=Gz
'       .GetInertia(arr)       — 惯量矩阵数组（kg·m²，9 个分量，行主序）：
'                                  arr(0)=Ixx, arr(1)=Ixy, arr(2)=Ixz
'                                  arr(3)=Iyx, arr(4)=Iyy, arr(5)=Iyz
'                                  arr(6)=Izx, arr(7)=Izy, arr(8)=Izz
'   · 测量为实时计算（transient），不在参数树中创建"惯量包络体"节点，
'     不修改零件文档，可安全运行。
'   · 测量对象为零件第一个几何体（Bodies.Item(1)，通常为"零件体"）。
'
' 先决条件：
'   · 零件文档已在 CATIA 中打开，且含有有效的实体几何（PartBody 非空）。
'   · CATIA SPA（惯量分析）模块已安装并授权。
'
' iParameters 用法（由 SystemService.ExecuteScript 传入，也可直接在宏编辑器中运行）：
'   iParameters — 目标零件的零件编号（PartNumber 字符串，可选）。
'     · 若提供且非空：遍历已打开的 PartDocument，按 PartNumber 定位并激活，
'       再执行测量。
'     · 若为空或省略：对 CATIA 当前活动文档执行。
'
' 输出：
'   成功时弹窗显示：零件编号、质量（kg）、重心 Gx/Gy/Gz（mm）、
'                   Ixx/Iyy/Izz/Ixy/Ixz/Iyz（kg·m²）
'   失败时弹窗显示具体错误信息，便于诊断。
' ============================================================

Sub CATMain(iParameters)

    ' ── 获取 CATIA 应用对象 ────────────────────────────────────────────────
    Dim CATIA
    Set CATIA = GetObject(, "CATIA.Application")

    ' ── 解析 iParameters：目标零件编号（PartNumber，可选）───────────────────
    Dim targetPN
    targetPN = ""
    On Error Resume Next
    targetPN = CStr(iParameters)
    If Err.Number <> 0 Then targetPN = ""
    Err.Clear
    On Error GoTo 0

    ' ── 定位目标 PartDocument ──────────────────────────────────────────────
    Dim partDoc
    Set partDoc = Nothing

    If targetPN <> "" Then
        ' 按零件编号在已打开文档中查找
        Dim i, found
        found = False
        On Error Resume Next
        For i = 1 To CATIA.Documents.Count
            Dim doc
            Set doc = CATIA.Documents.Item(i)
            If Err.Number = 0 And TypeName(doc) = "PartDocument" Then
                Dim pn
                pn = doc.Product.PartNumber
                If Err.Number = 0 And pn = targetPN Then
                    Set partDoc = doc
                    partDoc.Activate
                    found = True
                    Exit For
                End If
            End If
            Err.Clear
        Next
        On Error GoTo 0

        If Not found Then
            MsgBox "未找到零件编号为 [" & targetPN & "] 的 PartDocument。" & vbCrLf & _
                   "请确认该零件文档已在 CATIA 中打开。", _
                   vbExclamation, "auto_measure_inertia"
            Exit Sub
        End If
    Else
        ' 使用当前活动文档
        On Error Resume Next
        If CATIA.Documents.Count = 0 Then
            MsgBox "没有已打开的文档，已退出。", vbExclamation, "auto_measure_inertia"
            Exit Sub
        End If
        If TypeName(CATIA.ActiveDocument) <> "PartDocument" Then
            MsgBox "当前活动文档不是 PartDocument（类型=" & TypeName(CATIA.ActiveDocument) & "）。" & vbCrLf & _
                   "请先激活一个零件文档，或通过 iParameters 传入零件编号。", _
                   vbExclamation, "auto_measure_inertia"
            Exit Sub
        End If
        Set partDoc = CATIA.ActiveDocument
        On Error GoTo 0
    End If

    ' ── 获取 Part 对象与零件编号 ───────────────────────────────────────────
    Dim part
    Set part = partDoc.Part

    Dim actualPN
    On Error Resume Next
    actualPN = part.PartNumber
    If Err.Number <> 0 Or actualPN = "" Then actualPN = "(读取失败)"
    Err.Clear
    On Error GoTo 0

    ' ── 获取第一个几何体（零件体）引用 ─────────────────────────────────────
    Dim oBody
    On Error Resume Next
    Set oBody = part.Bodies.Item(1)
    If Err.Number <> 0 Or oBody Is Nothing Then
        MsgBox "零件 [" & actualPN & "] 无法访问 Bodies.Item(1)：" & vbCrLf & _
               "错误 " & Err.Number & "：" & Err.Description & vbCrLf & vbCrLf & _
               "请确认零件含有实体几何体（PartBody）。", _
               vbExclamation, "auto_measure_inertia"
        Err.Clear
        On Error GoTo 0
        Exit Sub
    End If
    On Error GoTo 0

    ' ── 创建到几何体的引用 ─────────────────────────────────────────────────
    Dim oRef
    On Error Resume Next
    Set oRef = part.CreateReferenceFromObject(oBody)
    If Err.Number <> 0 Or oRef Is Nothing Then
        MsgBox "无法为 Bodies.Item(1) 创建引用：" & vbCrLf & _
               "错误 " & Err.Number & "：" & Err.Description, _
               vbExclamation, "auto_measure_inertia"
        Err.Clear
        On Error GoTo 0
        Exit Sub
    End If
    On Error GoTo 0

    ' ── 获取 SPAWorkbench ──────────────────────────────────────────────────
    Dim oSPA
    On Error Resume Next
    Set oSPA = partDoc.GetWorkbench("SPAWorkbench")
    If Err.Number <> 0 Or oSPA Is Nothing Then
        MsgBox "无法获取 SPAWorkbench：" & vbCrLf & _
               "错误 " & Err.Number & "：" & Err.Description & vbCrLf & vbCrLf & _
               "请确认 CATIA SPA（惯量分析）模块已安装并授权。", _
               vbExclamation, "auto_measure_inertia"
        Err.Clear
        On Error GoTo 0
        Exit Sub
    End If
    On Error GoTo 0

    ' ── 通过 Measurable 接口读取惯量（实时测量，不修改文档）─────────────────
    ' 正确的 CATIA V5 SPA API（V5R20 及以上均支持）：
    '   .Mass                 — 质量，kg
    '   .GetCOGPosition(arr)  — 重心坐标，mm（arr(0)=Gx, arr(1)=Gy, arr(2)=Gz）
    '   .GetInertia(arr)      — 惯量矩阵，kg·m²（9 个分量，行主序 3×3）：
    '                             arr(0)=Ixx  arr(1)=Ixy  arr(2)=Ixz
    '                             arr(3)=Iyx  arr(4)=Iyy  arr(5)=Iyz
    '                             arr(6)=Izx  arr(7)=Izy  arr(8)=Izz
    ' 注意：GetCOGPosition 和 GetInertia 是 Sub（ByRef 数组参数），
    '        必须先声明数组再传入，不能用返回值接收。
    Dim oMeasurable
    On Error Resume Next
    Set oMeasurable = oSPA.GetMeasurable(oRef)
    If Err.Number <> 0 Or oMeasurable Is Nothing Then
        MsgBox "GetMeasurable() 失败：" & vbCrLf & _
               "错误 " & Err.Number & "：" & Err.Description & vbCrLf & vbCrLf & _
               "可能原因：零件体为空或无实体几何。", _
               vbExclamation, "auto_measure_inertia"
        Err.Clear
        On Error GoTo 0
        Exit Sub
    End If
    On Error GoTo 0

    Dim massVal
    massVal = "?"
    On Error Resume Next
    massVal = oMeasurable.Mass
    If Err.Number <> 0 Then
        MsgBox "读取 Measurable.Mass 失败：" & vbCrLf & _
               "错误 " & Err.Number & "：" & Err.Description & vbCrLf & vbCrLf & _
               "可能原因：零件体无实体几何（面积/体积为零）。", _
               vbExclamation, "auto_measure_inertia"
        Err.Clear
        On Error GoTo 0
        Exit Sub
    End If
    On Error GoTo 0

    Dim cogArr(2)
    On Error Resume Next
    oMeasurable.GetCOGPosition cogArr
    If Err.Number <> 0 Then
        cogArr(0) = "?": cogArr(1) = "?": cogArr(2) = "?"
        Err.Clear
    End If
    On Error GoTo 0

    Dim inertiaArr(8)
    On Error Resume Next
    oMeasurable.GetInertia inertiaArr
    If Err.Number <> 0 Then
        Dim k
        For k = 0 To 8: inertiaArr(k) = "?": Next
        Err.Clear
    End If
    On Error GoTo 0

    ' ── 汇报结果 ──────────────────────────────────────────────────────────
    Dim resultMsg
    resultMsg = "零件 [" & actualPN & "] 路径 A（SPA 实时测量）成功！" & vbCrLf & vbCrLf & _
                "── 质量 ──────────────────────────────────────────────────" & vbCrLf & _
                "  Mass              = " & FormatVal(massVal,    6) & " kg"    & vbCrLf & vbCrLf & _
                "── 重心（局部坐标系）────────────────────────────────────" & vbCrLf & _
                "  Gx                = " & FormatVal(cogArr(0),  4) & " mm"   & vbCrLf & _
                "  Gy                = " & FormatVal(cogArr(1),  4) & " mm"   & vbCrLf & _
                "  Gz                = " & FormatVal(cogArr(2),  4) & " mm"   & vbCrLf & vbCrLf & _
                "── 惯量矩阵（重心坐标系，kg·m²）────────────────────────" & vbCrLf & _
                "  Ixx               = " & FormatVal(inertiaArr(0), 6) & vbCrLf & _
                "  Iyy               = " & FormatVal(inertiaArr(4), 6) & vbCrLf & _
                "  Izz               = " & FormatVal(inertiaArr(8), 6) & vbCrLf & _
                "  Ixy               = " & FormatVal(inertiaArr(1), 6) & vbCrLf & _
                "  Ixz               = " & FormatVal(inertiaArr(2), 6) & vbCrLf & _
                "  Iyz               = " & FormatVal(inertiaArr(5), 6) & vbCrLf & vbCrLf & _
                "注：本次为实时测量，未在参数树中创建「惯量包络体」节点。" & vbCrLf & _
                "如需创建 Keep 测量，请在 CATIA SPA 工作台手动执行「测量惯量」" & vbCrLf & _
                "并勾选「保持测量」，之后 Python 端即可直接读取 Keep 参数。"

    MsgBox resultMsg, vbInformation, "auto_measure_inertia"

End Sub


' ============================================================
' FormatVal — 将数值格式化为指定小数位数的字符串；
'             若传入非数值（如 "?" 占位符）则原样返回
' ============================================================
Private Function FormatVal(v, decimals)
    If IsNumeric(v) Then
        FormatVal = FormatNumber(CDbl(v), decimals)
    Else
        FormatVal = CStr(v)
    End If
End Function
